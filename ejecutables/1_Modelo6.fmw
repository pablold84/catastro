FME workspace 1_Modelo6.fmw
Title: Modelo6

Parameters:
- schema = cabrales   # Esquema Base de datos (es necesario escribir el nombre)
- tablas = cabrales.DATOS_INICIALES cabrales.segipsa_placo
- sauce = G:\dgn\CABRALES\SAUCE\*.xlsx   # Entrada Sauce (Ruta archivos excel SAUCE, \*.xlsx lee todos los archivos de una carpeta)
- dxf = G:\dgn\CABRALES\FXCC\**\*.dxf   # DXF de entrada (\*.dxf lee todos los archivos de una carpeta)
- salida = $(FME_MF_DIR_USERTYPED)Salida   # Salida de archivos

Readers:
- XLSXR_1: XLSXR from $(sauce)

AttributeExposer_2
    ATTR_TABLE = accion,varchar(255),anio,int32,catastral,varchar(7),cod_incidencia,varchar(8),cod_incidencia_adicional,varchar(8),cod_via,int32,contrato_basado,varchar(255),control,int32,cp,varchar(50),del,varchar(2),documento,varchar(255),documentos_escaneados,varchar(255),dupli,varchar(50),entrada,date,exp,int32,exp_relacionados,varchar(255),factura,varchar(15),fecha_act_urbanist,date,fecha_alt,date,fecha_cert_finob,date,fecha_digit,date,fecha_grab,date,fecha_inf_ayunt,date,fecha_licencia,date,fecha_otras,date,fecha_proyecto,date,fecha_registro_exp,date,foto_croquis,buffer,id,int32,justif_fecha_alteracion,varchar(255),justif_superficie,varchar(255),lote,int32,modelo,varchar(255),mov,varchar(10),mun,varchar(3),nexp,int32,nom_mun,varchar(50),npoli,int32,observ_requer,varchar(255),observaciones,varchar(200),observaciones_ii,varchar(200),oper,varchar(50),oper_grab,varchar(50),orig_alter,varchar(1),ortofoto_1,varchar(4),proyecto,varchar(50),REFCAT,char(14),referencia,varchar(7),salida,date,sigla_via,varchar(50),situacion,varchar(50),tarifa,varchar(255),texto_etapa_aint,varchar(10485760),texto_etapa_reqe,varchar(10485760),texto_notif,varchar(10485760),tr_campo,varchar(255),tr_digi_grab,varchar(255),uu_fin,int32,ANY_ANTIG,int32,ANY_REFOR,int32,AP_CO_CO,buffer,CARGO,int32,CAT_PREDO,int32,DEL,int32,DES,buffer,ES,buffer,FC,int32,I_REFOR,buffer,id,int32,MUN,int32,ORD_CONS,int32,PLA,buffer,PUE,buffer,R1,buffer,R2,buffer,REFCAT,char(14),S_BRAS,int32,S_CONST,int32,S_CUB,int32,S_FINCA,int32,S_SRAS,int32,SUP_LOCAL,int32,TIPOL,buffer,U_CONS,buffer,USO,buffer,fme_feature_type,
    -> Tester_4
Note: Excel de SAUCE con la REFCAT
AttributeKeeper_6
    CREATE_BULK_MODE_FEATURES = NO
    KEEP_ATTRS = fme_basename,REFCAT
    -> AttributeManager_12
AttributeManager_12
    ATTR_TABLE:
      SET_TO filecopy_source_dataset (varchar(200)) = \\cartofs.seresco.red\rustica\dgn\@UpperCase($(schema))\SAUCE\@Value(fme_basename).csv
      SET_TO filecopy_dest_filename (varchar(200)) = @Value(REFCAT).csv
    -> DuplicateFilter_2
DuplicateFilter_2
    INPUT_ORDERED_CHOICE = No
    KEYATTR = REFCAT
    UNIQUE -> CSV [Output]
Note: Copia los CSV del servidor cartofs a la ruta seleccionada en salida
CSV: FeatureWriter
    DATASET = $(salida)\@Value(REFCAT)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = text/plain
    FILECOPY_OVERWRITE_FILE = YES
    FORMAT = FILECOPY
    TOTAL_FEATURES_WRITTEN_ATTR = _total_features_written
Junction [off]
    -> Sorter
Note: Ordeno por ORDEN/LOCAL
Sorter [off]
    GROUP_BY = REFCAT
    SORT_PARM = L NUMERIC ASCENDING
    SORTED -> AttributeManager_11
Note: Campos de salida
AttributeManager_11 [off]
    ATTR_TABLE:
      RENAME_SET_VALUE AD > CARGO (varchar(16))
      RENAME_SET_VALUE L > ORDEN (varchar(10))
      RENAME_SET_VALUE N > ESCALERA (varchar(12))
      RENAME_SET_VALUE O > PLANTA (varchar(16))
      RENAME_SET_VALUE P > PUERTA (varchar(15))
      RENAME_SET_VALUE T > TIPOLOGIA (varchar(15))
      RENAME_SET_VALUE U > CAT_PRED (varchar(15))
      RENAME_SET_VALUE S > USO (varchar(15))
      RENAME_SET_VALUE AA > SUPERFICIE (varchar(16))
      RENAME_SET_VALUE Q > UNIDAD_CONST (varchar(20))
      RENAME_SET_VALUE COEF > E_CONS (varchar(20))
      RENAME_SET_VALUE X > ANY_ANT (varchar(16))
      RENAME_SET_VALUE W > ANY_REF (varchar(15))
      REMOVE E (varchar(14))
    -> EXCEL_FICHA [Output00]
EXCEL_FICHA: FeatureWriter [off]
    DATASET = $(salida)\@Value(REFCAT)\@Value(REFCAT).xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = YES
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = Yes
    XLSXW_STRICT_SCHEMA_ADDITIONAL_ATTRIBUTE_MATCHING = yes
    XLSXW_TEMPLATEFILE = $(FME_MF_DIR)Plantilla\FICHA_RESUMEN_PLACO23 (Modelo6).xlsx
    XLSXW_TEMPLATE_SHEET = FICHA RESUMEN PLACO
    XLSXW_TRUNCATE_TABLE = No
    XLSXW_WRITER_MODE = Insert

Bookmark: POSTGIS
Creator_2
    GEOMTYPE = Geometry Object
    NUM = 1
    CREATED -> FeatureReader_2 [INITIATOR]
FeatureReader_2
    ATTRIBUTES = cabrales.DATOS_INICIALES,"id,DEL,MUN,R1,R2,ORD_CONS,CARGO,U_CONS,ES,PLA,PUE,USO,DES,I_REFOR,ANY_REFOR,ANY_ANTIG,SUP_LOCAL,TIPOL,CAT_PREDO,AP_CO_CO,S_FINCA,S_CONST,S_SRAS,S_BRAS,S_CUB,FC,REFCAT",cabrales.segipsa_placo,"proyecto,entrada,salida,fecha_alt,del,mun,nom_mun,cod_via,sigla_via,situacion,npoli,dupli,cp,referencia,catastral,nexp,exp,control,anio,modelo,uu_fin,oper,fecha_digit,oper_grab,fecha_grab,mov,tr_campo,tr_digi_grab,fecha_proyecto,fecha_licencia,fecha_act_urbanist,fecha_cert_finob,fecha_inf_ayunt,fecha_otras,ortofoto_1,justif_fecha_alteracion,justif_superficie,observaciones,observaciones_ii,observ_requer,exp_relacionados,lote,documentos_escaneados,cod_incidencia,orig_alter,fecha_registro_exp,cod_incidencia_adicional,accion,texto_notif,texto_etapa_aint,texto_etapa_reqe,factura,documento,tarifa,contrato_basado,foto_croquis,id,REFCAT"
    ATTR_ACCUM_MODE = Only Use Result
    COMBINE_GEOM = Use Result
    DATASET = SEGIPSA
    FEATURETYPES = $(tablas)
    FORMAT = POSTGRES
    ORDER_RESULTS = No
    OUTPUT_ADD_SCHEMA_ATTRIBUTES = NO
    OUTPUT_FEATURES_DISPLAY = Schema and Data Features
    POSTGRES_CREATE_FEATURE_TABLES_FROM_DATA = Yes
    POSTGRES_FEATURES_PER_FETCH = 10000
    POSTGRES_NAMED_CONNECTION = Segipsa
    POSTGRES_QUERY_FEATURE_TYPES_FOR_MERGE_FILTERS = Yes
    POSTGRES_READ_TIME_WITH_TIMEZONE = Yes
    POSTGRES_SCHEMAS_FOR_TABLE_LISTING = $(schema)
    <OTHER> -> AttributeExposer_2

Bookmark: FICHA RESUMEN - DATOS INICIALES
Tester_4
    BOOL_OP = OR
    TEST_CLAUSE = TEST @Value(accion) != CIER
    TEST_MODE = TEST
    PASSED -> DateTimeConverter
DateTimeConverter
    DATETIME_ATTR = fecha_act_urbanist fecha_alt fecha_cert_finob fecha_digit fecha_grab fecha_inf_ayunt fecha_licencia fecha_otras fecha_proyecto fecha_registro_exp
    OUT_FORMAT = %d/%m/%Y
    PASSTHROUGH = YES
    REPAIR_INPUT = YES
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(fme_feature_type) CONTAINS INICIALES",INICIALES,"BOOL_OP,OR,COMPOSITE_TEST,""""""1"""""",TEST_CLAUSE,CASE_INSENSITIVE_TEST @Value(fme_feature_type) CONTAINS placo",PLACO
    INICIALES -> AttributeManager
    PLACO -> AttributeManager_2
Note: JOIN por REFCAT
FeatureJoiner [off]
    ATTR_CONFLICT_RES = Prefer Left
    GEOMETRY_HANDLING = Prefer Left
    JOIN_KEYS = REFCAT REFERENCIA CATASTRAL AUTO
    JOIN_MODE = Inner
    JOINED -> AttributeManager_6
    <REJECTED> -> Junction_2
AttributeManager_6 [off]
    ATTR_TABLE:
      SET_TO GERENCIA-MUNICIPIO (varchar(200)) = GERENCIA-MUNICIPIO: @Value(GERENCIA-MUNICIPIO)
      SET_TO REFERENCIA CATASTRAL (varchar(200)) = REFERENCIA CATASTRAL: @Value(REFERENCIA CATASTRAL)
      SET_TO Nº EXPEDIENTE (varchar(200)) = Nº EXPEDIENTE: @Value(Nº EXPEDIENTE)
      SET_TO DIRECCION (varchar(200)) = DIRECCIÓN: @Value(DIRECCION)
      SET_TO DOCUMENTACIÓN INCORPORADA/PROYECTO_OBRA (datetime) = FECHA: @Value(DOCUMENTACIÓN INCORPORADA/PROYECTO_OBRA)
      SET_TO DOCUMENTACIÓN INCORPORADA/CERTIFI_OBRA (datetime) = FECHA: @Value(DOCUMENTACIÓN INCORPORADA/CERTIFI_OBRA)
      SET_TO DOCUMENTACIÓN INCORPORADA/LIC_OBRA (datetime) = FECHA: @Value(DOCUMENTACIÓN INCORPORADA/LIC_OBRA)
      SET_TO DOCUMENTACIÓN INCORPORADA/INF_AYTO (datetime) = FECHA: @Value(DOCUMENTACIÓN INCORPORADA/INF_AYTO)
      SET_TO DOCUMENTACIÓN INCORPORADA/DECLARA (datetime) = FECHA: @Value(DOCUMENTACIÓN INCORPORADA/DECLARA)
      SET_TO DOCUMENTACIÓN INCORPORADA/OTRAS (datetime) = FECHA: @Value(DOCUMENTACIÓN INCORPORADA/OTRAS)
      SET_TO FECHA ALTERACIÓN/FECHA (datetime) = FECHA: @Value(FECHA ALTERACIÓN/FECHA)
      SET_TO FECHA ALTERACIÓN/MOTI (datetime) = MOTIVACIÓN: @Value(FECHA ALTERACIÓN/MOTI)
      REMOVE accion (varchar(255))
      REMOVE anio (int32)
      REMOVE catastral (varchar(7))
      REMOVE cod_incidencia (varchar(8))
      REMOVE cod_incidencia_adicional (varchar(8))
      REMOVE cod_via (int32)
      REMOVE contrato_basado (varchar(255))
      REMOVE control (int32)
      REMOVE cp (varchar(50))
      REMOVE del (varchar(2))
      REMOVE documento (varchar(255))
      REMOVE documentos_escaneados (varchar(255))
      REMOVE dupli (varchar(50))
      REMOVE entrada (date)
      REMOVE exp (int32)
      REMOVE exp_relacionados (varchar(255))
      REMOVE factura (varchar(15))
      REMOVE fecha_act_urbanist (buffer)
      REMOVE fecha_alt (buffer)
      REMOVE fecha_cert_finob (buffer)
      REMOVE fecha_digit (buffer)
      REMOVE fecha_grab (buffer)
      REMOVE fecha_inf_ayunt (buffer)
      REMOVE fecha_licencia (buffer)
      REMOVE fecha_otras (buffer)
      REMOVE fecha_proyecto (buffer)
      REMOVE fecha_registro_exp (buffer)
      REMOVE foto_croquis (buffer)
      REMOVE justif_fecha_alteracion (varchar(255))
      REMOVE justif_superficie (varchar(255))
      REMOVE lote (int32)
      REMOVE modelo (varchar(255))
      REMOVE mov (varchar(10))
      REMOVE mun (varchar(3))
      REMOVE nexp (int32)
      REMOVE nom_mun (varchar(50))
      REMOVE npoli (int32)
      REMOVE observ_requer (varchar(255))
      REMOVE observaciones (varchar(200))
      REMOVE observaciones_ii (varchar(200))
      REMOVE oper (varchar(50))
      REMOVE oper_grab (varchar(50))
      REMOVE orig_alter (varchar(1))
      REMOVE ortofoto_1 (varchar(4))
      REMOVE proyecto (varchar(50))
      REMOVE referencia (varchar(7))
      REMOVE salida (date)
      REMOVE sigla_via (varchar(50))
      REMOVE situacion (varchar(50))
      REMOVE tarifa (varchar(255))
      REMOVE texto_etapa_aint (varchar(10485760))
      REMOVE texto_etapa_reqe (varchar(10485760))
      REMOVE texto_notif (varchar(10485760))
      REMOVE tr_campo (varchar(255))
      REMOVE tr_digi_grab (varchar(255))
      REMOVE uu_fin (int32)
      REMOVE fme_feature_type (varchar(200))
    -> EXCEL_FICHA [Output]
Junction_2 [off]

Bookmark: DATOS
AttributeManager_2
    ATTR_TABLE:
      SET_TO GERENCIA-MUNICIPIO (varchar(200)) = @Value(del)@Value(mun)
      SET_TO REFERENCIA CATASTRAL (varchar(200)) = @Value(referencia)@Value(catastral)
      SET_TO Nº EXPEDIENTE (varchar(200)) = @Value(exp).@Value(control)/@Value(anio)
      SET_TO DIRECCION (varchar(200)) = @Value(sigla_via) @Value(situacion) @Value(npoli)@Value(dupli)@Value(cp)
      SET_TO ALTERACIÓN PROPUESTA (varchar(200)) = @Value(cod_incidencia)/@Value(cod_incidencia_adicional)
      SET_TO ACTUACIONES PREVIAS/GABINETE (varchar(200)) = @Value(tr_digi_grab)
      SET_TO ACTUACIONES PREVIAS/CAMPO (varchar(200)) = @Value(tr_campo)
      SET_TO DOCUMENTACIÓN INCORPORADA/PROYECTO_OBRA (datetime) = @Value(fecha_proyecto)
      SET_TO DOCUMENTACIÓN INCORPORADA/CERTIFI_OBRA (datetime) = @Value(fecha_cert_finob)
      SET_TO DOCUMENTACIÓN INCORPORADA/LIC_OBRA (datetime) = @Value(fecha_licencia)
      SET_TO DOCUMENTACIÓN INCORPORADA/INF_AYTO (datetime) = @Value(fecha_inf_ayunt)
      SET_TO DOCUMENTACIÓN INCORPORADA/DECLARA (datetime) = @Value(fecha_act_urbanist)
      SET_TO DOCUMENTACIÓN INCORPORADA/OTRAS (datetime) = @Value(fecha_otras)
      SET_TO FECHA ALTERACIÓN/FECHA (datetime) = @Value(fecha_alt)
      SET_TO FECHA ALTERACIÓN/MOTI (datetime) = @Value(justif_fecha_alteracion)
      SET_TO OBSERVACIONES (varchar(200)) = @Value(observaciones)
      REMOVE proyecto (varchar(50))
      REMOVE entrada (date)
      REMOVE salida (date)
      REMOVE fecha_alt (buffer)
      REMOVE del (varchar(2))
      REMOVE mun (varchar(3))
      REMOVE nom_mun (varchar(50))
      REMOVE cod_via (int32)
      REMOVE sigla_via (varchar(50))
      REMOVE situacion (varchar(50))
      REMOVE npoli (int32)
      REMOVE dupli (varchar(50))
      REMOVE cp (varchar(50))
      REMOVE referencia (varchar(7))
      REMOVE catastral (varchar(7))
      REMOVE nexp (int32)
      REMOVE exp (int32)
      REMOVE control (int32)
      REMOVE anio (int32)
      REMOVE modelo (varchar(255))
      REMOVE uu_fin (int32)
      REMOVE oper (varchar(50))
      REMOVE fecha_digit (buffer)
      REMOVE oper_grab (varchar(50))
      REMOVE fecha_grab (buffer)
      REMOVE mov (varchar(10))
      REMOVE tr_campo (varchar(255))
      REMOVE tr_digi_grab (varchar(255))
      REMOVE fecha_proyecto (buffer)
      REMOVE fecha_licencia (buffer)
      REMOVE fecha_act_urbanist (buffer)
      REMOVE fecha_cert_finob (buffer)
      REMOVE fecha_inf_ayunt (buffer)
      REMOVE fecha_otras (buffer)
      REMOVE ortofoto_1 (varchar(4))
      REMOVE justif_fecha_alteracion (varchar(255))
      REMOVE justif_superficie (varchar(255))
      REMOVE observaciones (varchar(200))
      REMOVE observaciones_ii (varchar(200))
      REMOVE observ_requer (varchar(255))
      REMOVE exp_relacionados (varchar(255))
      REMOVE lote (int32)
      REMOVE documentos_escaneados (varchar(255))
      REMOVE cod_incidencia (varchar(8))
      REMOVE orig_alter (varchar(1))
      REMOVE fecha_registro_exp (buffer)
      REMOVE cod_incidencia_adicional (varchar(8))
      REMOVE accion (varchar(255))
      REMOVE texto_notif (varchar(10485760))
      REMOVE texto_etapa_aint (varchar(10485760))
      REMOVE texto_etapa_reqe (varchar(10485760))
      REMOVE factura (varchar(15))
      REMOVE documento (varchar(255))
      REMOVE tarifa (varchar(255))
      REMOVE contrato_basado (varchar(255))
      REMOVE id (int32)
      REMOVE REFCAT (char(14))
      REMOVE ANY_ANTIG (int32)
      REMOVE ANY_REFOR (int32)
      REMOVE AP_CO_CO (buffer)
      REMOVE CARGO (int32)
      REMOVE CAT_PREDO (int32)
      REMOVE DEL (int32)
      REMOVE DES (buffer)
      REMOVE ES (buffer)
      REMOVE FC (int32)
      REMOVE I_REFOR (buffer)
      REMOVE MUN (int32)
      REMOVE ORD_CONS (int32)
      REMOVE PLA (buffer)
      REMOVE PUE (buffer)
      REMOVE R1 (buffer)
      REMOVE R2 (buffer)
      REMOVE S_BRAS (int32)
      REMOVE S_CONST (int32)
      REMOVE S_CUB (int32)
      REMOVE S_FINCA (int32)
      REMOVE S_SRAS (int32)
      REMOVE SUP_LOCAL (int32)
      REMOVE TIPOL (buffer)
      REMOVE U_CONS (buffer)
      REMOVE USO (buffer)
    -> FeatureJoiner [RIGHT]
    -> AttributeKeeper_4
AttributeManager
    ATTR_TABLE:
      SET_TO LOCAL (varchar(200)) = @Value(ORD_CONS)
      SET_TO ESC. (varchar(200)) = @Value(ES)
      SET_TO PL (varchar(200)) = @Value(PLA)
      SET_TO PTA. (varchar(200)) = @Value(PUE)
      SET_TO TIP. (1) (varchar(200)) = @Value(TIPOL)
      SET_TO CAT. (1) (varchar(200)) = @Value(CAT_PREDO)
      SET_TO USO (2) (varchar(200)) = @Value(DES)
      SET_TO SUP. (m²) (varchar(200)) = @Value(SUP_LOCAL)
      SET_TO U. C. (varchar(200)) = @Value(U_CONS)
      SET_TO E. CONS. (1) (varchar(200)) = @Value(AP_CO_CO)
      SET_TO ANT. (6) (varchar(200)) = @Value(ANY_ANTIG)
      REMOVE id (int32)
      REMOVE DEL (int32)
      REMOVE MUN (int32)
      REMOVE R1 (buffer)
      REMOVE R2 (buffer)
      REMOVE ORD_CONS (int32)
      REMOVE U_CONS (buffer)
      REMOVE ES (buffer)
      REMOVE PLA (buffer)
      REMOVE PUE (buffer)
      REMOVE USO (buffer)
      REMOVE DES (buffer)
      REMOVE I_REFOR (buffer)
      REMOVE ANY_REFOR (int32)
      REMOVE ANY_ANTIG (int32)
      REMOVE SUP_LOCAL (int32)
      REMOVE TIPOL (buffer)
      REMOVE CAT_PREDO (int32)
      REMOVE AP_CO_CO (buffer)
      REMOVE S_FINCA (int32)
      REMOVE S_CONST (int32)
      REMOVE S_SRAS (int32)
      REMOVE S_BRAS (int32)
      REMOVE S_CUB (int32)
      REMOVE FC (int32)
    USER_EXPOSED_ATTRIBUTES = id,DEL,MUN,R1,R2,ORD_CONS,CARGO,U_CONS,ES,PLA,PUE,USO,DES,I_REFOR,ANY_REFOR,ANY_ANTIG,SUP_LOCAL,TIPOL,CAT_PREDO,AP_CO_CO,S_FINCA,S_CONST,S_SRAS,S_BRAS,S_CUB,FC,REFCAT
    -> FeatureJoiner [LEFT]

Bookmark: FileCopy
AttributeKeeper_4
    CREATE_BULK_MODE_FEATURES = NO
    KEEP_ATTRS = foto_croquis,REFERENCIA CATASTRAL
    -> StringReplacer_2
StringReplacer_2
    CASE = NO
    FIND_TEXT = /
    NO_MATCH = _FME_NO_OP_
    REGEXP = NO
    REPLACE_TEXT = \
    SRC_ATTRS = foto_croquis
    -> AttributeManager_9
AttributeManager_9
    ATTR_TABLE:
      SET_TO filecopy_source_dataset (varchar(200)) = \\cartofs.seresco.red\rustica\dgn\@UpperCase($(schema))\@Value(foto_croquis)
      SET_TO filecopy_dest_filename (varchar(200)) = @Value(REFERENCIA CATASTRAL).jpg
    -> JPG [Output]
Note: Copia las imagenes del servidor cartofs a la ruta seleccionada en salida
JPG: FeatureWriter
    DATASET = $(salida)\@Value(REFERENCIA CATASTRAL)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = text/plain
    FILECOPY_OVERWRITE_FILE = YES
    FORMAT = FILECOPY
    TOTAL_FEATURES_WRITTEN_ATTR = _total_features_written

Bookmark: SAUCE
33_586633_22 (reader XLSXR_1)
    attributes: EXPEDIENTE char(22), B char(28), C char(19), D char(17), E char(14), F char(16), G char(14), H char(13), I char(20), J char(17), K char(13), L char(10), M char(11), N char(12), O char(16), P char(15), Q char(20), R char(15), S char(15), T char(15), U char(15), V char(15), W char(15), X char(16), Y char(16), Z char(15), AA char(16), AB char(12), AC char(14), AD char(16),
      AE char(17), AF char(13), AG char(14), AH char(14), AI char(12), AJ char(14), AK char(14), AL char(25), AM char(12), AN char(19), AO char(16), AP char(17), AQ char(16), AR char(18), AS char(12), AT char(16), AU char(12), AV char(14), AW char(13), AX char(15), AY char(15), AZ char(10), BA char(11), BB char(8), BC char(17), BD char(11), BE char(9), BF char(20), BG char(22), BH char(12),
      BI char(12), BJ char(12), BK char(11), BL char(12), BM char(12), BN char(13), BO char(15), BP char(15), BQ char(17), BR char(9), BS char(14), BT char(10), BU char(11), BV char(14), BW char(18), BX char(9), BY char(11), BZ char(14), CA char(11), CB char(11), CC char(12), CD char(4), CE char(12), CF char(7), CG char(6), CH char(5), CI char(9), CJ char(14), CK char(15), CL char(20),
      CM char(8), CN char(12), CO char(9), CP char(9), CQ char(9), CR char(10), CS char(14), CT char(10), CU char(15), CV char(7), CW char(15), CX char(13), CY char(6)
    -> AttributeCreator_3
    -> Tester_6
    -> FeatureJoiner_7 [LEFT]
    -> Tester_8
    -> FeatureJoiner_9 [LEFT]
Note: HOJAS CON FORMATO SAUCE DIFERENTE
Tester_8
    BOOL_OP = OR
    TEST_CLAUSE = TEST @Value(EXPEDIENTE) = CULTIVOS
    TEST_MODE = TEST
    PASSED -> AttributeKeeper_5
AttributeKeeper_5
    CREATE_BULK_MODE_FEATURES = NO
    KEEP_ATTRS = fme_basename
    -> FeatureJoiner_9 [RIGHT]
Note: Divido hojas por su tipologia
FeatureJoiner_9
    ATTR_CONFLICT_RES = Prefer Left
    GEOMETRY_HANDLING = Prefer Left
    JOIN_KEYS = fme_basename fme_basename AUTO
    JOIN_MODE = Inner
    JOINED -> StringSearcher_7
    JOINED -> StringSearcher_8
    UNJOINED_LEFT -> StringSearcher
    UNJOINED_LEFT -> StringSearcher_2
Note: Max y min
StatisticsCalculator_4
    ATTR_ACCUM_MODE = None
    CALCULATION_MODE = NUMERIC
    FEAT_STATS = xlsx_row_id,NUMERIC_MODE,MIN,MAX,,,,,,,,,,,
    GROUP_BY = fme_basename
    SUMMARY -> AttributeManager_10
AttributeManager_10
    ATTR_TABLE:
      SET_TO Rango (varchar(200)) = (@Value(xlsx_row_id.min),@Value(xlsx_row_id.max))
      SET_TO Merge (uint8) = 1
      REMOVE xlsx_row_id.min (real64)
      REMOVE xlsx_row_id.max (real64)
    -> FeatureJoiner_10 [RIGHT]
Note: Max y min
StatisticsCalculator
    ATTR_ACCUM_MODE = None
    CALCULATION_MODE = NUMERIC
    FEAT_STATS = xlsx_row_id,NUMERIC_MODE,MIN,MAX,,,,,,,,,,,
    GROUP_BY = fme_basename
    SUMMARY -> AttributeManager_4
AttributeManager_4
    ATTR_TABLE:
      SET_TO Rango (varchar(200)) = (@Value(xlsx_row_id.min),@Value(xlsx_row_id.max))
      SET_TO Merge (uint8) = 1
      REMOVE xlsx_row_id.min (real64)
      REMOVE xlsx_row_id.max (real64)
    -> FeatureJoiner_3 [RIGHT]
Note: Datos completos SAUCE
AttributeCreator_3
    ATTR_TABLE = SET_TO Merge (uint8) = 1
    -> FeatureJoiner_3 [LEFT]
    -> FeatureJoiner_2 [LEFT]
    -> FeatureJoiner_8 [LEFT]
    -> FeatureJoiner_10 [LEFT]
Note: HOJAS CON FORMATO SAUCE DIFERENTE
Tester_6
    BOOL_OP = OR
    TEST_CLAUSE = TEST @Value(EXPEDIENTE) = REPARTO CONSTRUCCIONES EN CONSTRUCCIONES
    TEST_MODE = TEST
    PASSED -> AttributeKeeper_3
AttributeKeeper_3
    CREATE_BULK_MODE_FEATURES = NO
    KEEP_ATTRS = fme_basename
    -> FeatureJoiner_7 [RIGHT]
FeatureJoiner_7
    ATTR_CONFLICT_RES = Prefer Left
    GEOMETRY_HANDLING = Prefer Left
    JOIN_KEYS = fme_basename fme_basename AUTO
    JOIN_MODE = Inner
    JOINED -> StringSearcher_5
    JOINED -> StringSearcher_6
    UNJOINED_LEFT -> StringSearcher_3
    UNJOINED_LEFT -> StringSearcher_4
Note: Max y min
StatisticsCalculator_2
    ATTR_ACCUM_MODE = None
    CALCULATION_MODE = NUMERIC
    FEAT_STATS = xlsx_row_id,NUMERIC_MODE,MIN,MAX,,,,,,,,,,,
    GROUP_BY = fme_basename
    SUMMARY -> AttributeManager_3
AttributeManager_3
    ATTR_TABLE:
      SET_TO Rango (varchar(200)) = (@Value(xlsx_row_id.min),@Value(xlsx_row_id.max))
      SET_TO Merge (uint8) = 1
      REMOVE xlsx_row_id.max (real64)
    -> FeatureJoiner_2 [RIGHT]
Note: Max y min
StatisticsCalculator_3
    ATTR_ACCUM_MODE = None
    CALCULATION_MODE = NUMERIC
    FEAT_STATS = xlsx_row_id,NUMERIC_MODE,MIN,MAX,,,,,,,,,,,
    GROUP_BY = fme_basename
    SUMMARY -> AttributeManager_5
AttributeManager_5
    ATTR_TABLE:
      SET_TO Rango (varchar(200)) = (@Value(xlsx_row_id.min),@Value(xlsx_row_id.max))
      SET_TO Merge (uint8) = 1
      REMOVE xlsx_row_id.max (real64)
    -> FeatureJoiner_8 [RIGHT]
AttributeKeeper [off]
    CREATE_BULK_MODE_FEATURES = NO
    KEEP_ATTRS = AA,L,N,O,P,Q,S,T,U,W,X,REFCAT,fme_basename,AD
    -> FeatureJoiner_6 [LEFT]
AttributeKeeper_2 [off]
    CREATE_BULK_MODE_FEATURES = NO
    KEEP_ATTRS = Q,REFCAT,E,fme_basename
    -> DuplicateFilter
DuplicateFilter [off]
    INPUT_ORDERED_CHOICE = No
    KEYATTR = REFCAT E
    UNIQUE -> AttributeRenamer
AttributeRenamer [off]
    ATTR_TABLE = RENAME_SET_DEFAULT Q > COEF
    KEEP_RENAMED_ONLY = no
    MISSING_INPUT_ATTRS = REMOVE
    -> Tester_10
Tester_10 [off]
    BOOL_OP = OR
    TEST_CLAUSE = TEST COEF ATTRIBUTE_HAS_A_VALUE ""
    TEST_MODE = TEST
    PASSED -> FeatureJoiner_6 [RIGHT]
Note: Uno los datos de SAUCE por su REFCAT
FeatureJoiner_6 [off]
    ATTR_CONFLICT_RES = Prefer Left
    GEOMETRY_HANDLING = Prefer Left
    JOIN_KEYS = REFCAT REFCAT AUTO Q E AUTO
    JOIN_MODE = Inner
    JOINED -> Junction
    UNJOINED_LEFT -> Junction

Bookmark: CONSTRUC-CULTIVOS
StringSearcher_7
    CASE = yes
    MATCHED_RESULT_ATTR = _first_match
    REGEXP = ^CONSTRUCCIONES
    STRING_TO_SEARCH = @Value(EXPEDIENTE)
    MATCHED -> StatisticsCalculator_4
StringSearcher_8
    CASE = no
    MATCHED_RESULT_ATTR = _first_match
    REGEXP = CULTIVOS
    STRING_TO_SEARCH = @Value(EXPEDIENTE)
    MATCHED -> StatisticsCalculator_4

Bookmark: CONSTRUC-TITULARES
StringSearcher
    CASE = yes
    MATCHED_RESULT_ATTR = _first_match
    REGEXP = ^CONSTRUCCIONES
    STRING_TO_SEARCH = @Value(EXPEDIENTE)
    MATCHED -> StatisticsCalculator
StringSearcher_2
    CASE = no
    MATCHED_RESULT_ATTR = _first_match
    REGEXP = TITULARES
    STRING_TO_SEARCH = @Value(EXPEDIENTE)
    MATCHED -> StatisticsCalculator

Bookmark: Añado rango a datos
FeatureJoiner_10
    ATTR_CONFLICT_RES = Prefer Left
    GEOMETRY_HANDLING = Prefer Left
    JOIN_KEYS = Merge Merge AUTO fme_basename fme_basename AUTO
    JOIN_MODE = Inner
    JOINED -> Tester_9
FeatureJoiner_3
    ATTR_CONFLICT_RES = Prefer Left
    GEOMETRY_HANDLING = Prefer Left
    JOIN_KEYS = Merge Merge AUTO fme_basename fme_basename AUTO
    JOIN_MODE = Inner
    JOINED -> Tester
FeatureJoiner_2
    ATTR_CONFLICT_RES = Prefer Left
    GEOMETRY_HANDLING = Prefer Left
    JOIN_KEYS = Merge Merge AUTO fme_basename fme_basename AUTO
    JOIN_MODE = Inner
    JOINED -> Tester_2
FeatureJoiner_8
    ATTR_CONFLICT_RES = Prefer Left
    GEOMETRY_HANDLING = Prefer Left
    JOIN_KEYS = Merge Merge AUTO fme_basename fme_basename AUTO
    JOIN_MODE = Inner
    JOINED -> Tester_7

Bookmark: FILTRO por rango
Tester_9
    BOOL_OP = COMPOSITE
    COMPOSITE_TEST = 1 AND 2
    TEST_CLAUSE:
      NUM_TEST @Value(xlsx_row_id) RANGE @Value(Rango)
      NUM_TEST I ATTRIBUTE_HAS_A_VALUE ""
    TEST_MODE = NUM_TEST
    PASSED -> FeatureJoiner_4 [LEFT]
Tester
    BOOL_OP = COMPOSITE
    COMPOSITE_TEST = 1 AND 2
    TEST_CLAUSE:
      NUM_TEST @Value(xlsx_row_id) RANGE @Value(Rango)
      NUM_TEST I ATTRIBUTE_HAS_A_VALUE ""
    TEST_MODE = NUM_TEST
    PASSED -> FeatureJoiner_4 [LEFT]
Tester_2
    BOOL_OP = AND
    TEST_CLAUSE:
      NUM_TEST @Value(xlsx_row_id) RANGE @Value(Rango)
      NUM_TEST C ATTRIBUTE_HAS_A_VALUE ""
    TEST_MODE = NUM_TEST
    PASSED -> FeatureJoiner_5 [LEFT]
    PASSED -> Tester_3
Tester_7
    BOOL_OP = AND
    TEST_CLAUSE:
      NUM_TEST @Value(xlsx_row_id) RANGE @Value(Rango)
      NUM_TEST C ATTRIBUTE_HAS_A_VALUE ""
    TEST_MODE = NUM_TEST
    PASSED -> Tester_3
    PASSED -> FeatureJoiner_5 [LEFT]

Bookmark: CONSTRUC-VIAS
StringSearcher_3
    CASE = no
    MATCHED_RESULT_ATTR = _first_match
    REGEXP = UNIDADES CONSTRUCTIVAS
    STRING_TO_SEARCH = @Value(EXPEDIENTE)
    MATCHED -> StatisticsCalculator_2
StringSearcher_4
    CASE = no
    MATCHED_RESULT_ATTR = _first_match
    REGEXP = VIAS
    STRING_TO_SEARCH = @Value(EXPEDIENTE)
    MATCHED -> StatisticsCalculator_2

Bookmark: REPARTO-VIAS
StringSearcher_5
    CASE = no
    MATCHED_RESULT_ATTR = _first_match
    REGEXP = REPARTO CONSTRUCCIONES EN CONSTRUCCIONES
    STRING_TO_SEARCH = @Value(EXPEDIENTE)
    MATCHED -> StatisticsCalculator_3
StringSearcher_6
    CASE = no
    MATCHED_RESULT_ATTR = _first_match
    REGEXP = VIAS
    STRING_TO_SEARCH = @Value(EXPEDIENTE)
    MATCHED -> StatisticsCalculator_3

Bookmark: REFCAT
Note: Extraccion de REFCAT
Tester_3
    BOOL_OP = OR
    TEST_CLAUSE = TEST @Value(xlsx_row_id) = @Evaluate(@Value(xlsx_row_id.min)+2)
    TEST_MODE = TEST
    PASSED -> AttributeManager_7
Note: MODIFICAR REFCAT
AttributeManager_7
    ATTR_TABLE:
      SET_TO REFCAT (varchar(14)) = @Value(C)@Value(D)
      REMOVE EXPEDIENTE (varchar(22))
      REMOVE B (varchar(28))
      REMOVE C (varchar(19))
      REMOVE D (varchar(17))
      REMOVE E (varchar(14))
      REMOVE F (varchar(16))
      REMOVE G (varchar(14))
      REMOVE H (varchar(13))
      REMOVE I (varchar(20))
      REMOVE J (varchar(17))
      REMOVE K (varchar(13))
      REMOVE L (varchar(10))
      REMOVE M (varchar(11))
      REMOVE N (varchar(12))
      REMOVE O (varchar(16))
      REMOVE P (varchar(15))
      REMOVE Q (varchar(20))
      REMOVE R (varchar(15))
      REMOVE S (varchar(15))
      REMOVE T (varchar(15))
      REMOVE U (varchar(15))
      REMOVE V (varchar(15))
      REMOVE W (varchar(15))
      REMOVE X (varchar(16))
      REMOVE Y (varchar(16))
      REMOVE Z (varchar(15))
      REMOVE AA (varchar(16))
      REMOVE AB (varchar(12))
      REMOVE AC (varchar(14))
      REMOVE AD (varchar(16))
      REMOVE AE (varchar(17))
      REMOVE AF (varchar(13))
      REMOVE AG (varchar(14))
      REMOVE AH (varchar(14))
      REMOVE AI (varchar(12))
      REMOVE AJ (varchar(14))
      REMOVE AK (varchar(14))
      REMOVE AL (varchar(25))
      REMOVE AM (varchar(12))
      REMOVE AN (varchar(19))
      REMOVE AO (varchar(16))
      REMOVE AP (varchar(17))
      REMOVE AQ (varchar(16))
      REMOVE AR (varchar(18))
      REMOVE AS (varchar(12))
      REMOVE AT (varchar(16))
      REMOVE AU (varchar(12))
      REMOVE AV (varchar(14))
      REMOVE AW (varchar(13))
      REMOVE AX (varchar(15))
      REMOVE AY (varchar(15))
      REMOVE AZ (varchar(10))
      REMOVE BA (varchar(11))
      REMOVE BB (varchar(8))
      REMOVE BC (varchar(17))
      REMOVE BD (varchar(11))
      REMOVE BE (varchar(9))
      REMOVE BF (varchar(20))
      REMOVE BG (varchar(22))
      REMOVE BH (varchar(12))
      REMOVE BI (varchar(12))
      REMOVE BJ (varchar(12))
      REMOVE BK (varchar(11))
      REMOVE BL (varchar(12))
      REMOVE BM (varchar(12))
      REMOVE BN (varchar(13))
      REMOVE BO (varchar(15))
      REMOVE BP (varchar(15))
      REMOVE BQ (varchar(17))
      REMOVE BR (varchar(9))
      REMOVE BS (varchar(14))
      REMOVE BT (varchar(10))
      REMOVE BU (varchar(11))
      REMOVE BV (varchar(14))
      REMOVE BW (varchar(18))
      REMOVE BX (varchar(9))
      REMOVE BY (varchar(11))
      REMOVE BZ (varchar(14))
      REMOVE CA (varchar(11))
      REMOVE CB (varchar(11))
      REMOVE CC (varchar(12))
      REMOVE CD (varchar(4))
      REMOVE CE (varchar(12))
      REMOVE CF (varchar(7))
      REMOVE CG (varchar(6))
      REMOVE CH (varchar(5))
      REMOVE CI (varchar(9))
      REMOVE CJ (varchar(14))
      REMOVE CK (varchar(15))
      REMOVE CL (varchar(20))
      REMOVE CM (varchar(8))
      REMOVE CN (varchar(12))
      REMOVE CO (varchar(9))
      REMOVE CP (varchar(9))
      REMOVE CQ (varchar(9))
      REMOVE CR (varchar(10))
      REMOVE CS (varchar(14))
      REMOVE CT (varchar(10))
      REMOVE CU (varchar(15))
      REMOVE CV (varchar(7))
      REMOVE CW (varchar(15))
      REMOVE CX (varchar(13))
      REMOVE CY (varchar(6))
      REMOVE fme_feature_type (varchar(50))
      REMOVE xlsx_row_id (number(11,0))
      REMOVE Rango (varchar(200))
      REMOVE xlsx_row_id.min (real64)
    -> FeatureJoiner_4 [RIGHT]
    -> FeatureJoiner_5 [RIGHT]
    -> AttributeKeeper_6

Bookmark: Añado REFCAT
FeatureJoiner_4 [off]
    ATTR_CONFLICT_RES = Prefer Left
    GEOMETRY_HANDLING = Prefer Left
    JOIN_KEYS = Merge Merge AUTO fme_basename fme_basename AUTO
    JOIN_MODE = Inner
    JOINED -> AttributeKeeper
FeatureJoiner_5 [off]
    ATTR_CONFLICT_RES = Prefer Left
    GEOMETRY_HANDLING = Prefer Left
    JOIN_KEYS = Merge Merge AUTO fme_basename fme_basename AUTO
    JOIN_MODE = Inner
    JOINED -> AttributeKeeper_2

Bookmark: CROQUIS
Creator
    GEOMTYPE = Geometry Object
    NUM = 1
    CREATED -> FeatureReader [INITIATOR]
FeatureReader
    ACAD_ACAD_EXPOSE_FORMAT_ATTRS = fme_feature_type,char(50) autocad_source_filename,string fme_basename,char(50)
    ACAD_ALLOW_DASH_CHAR_IN_ATTR_NAMES = yes
    ACAD_ALL_MERGED_FILTERS_NEED_NO_DEFS = Yes
    ACAD_APPLY_WORLD_FILE = no
    ACAD_APPLY_WORLD_FILE_TO_ATTRS = YES
    ACAD_CONVERT_ZERO_LENGTH_ARCS_TO_POINTS = yes
    ACAD_EVALUATE_MLINE_GEOM = no
    ACAD_EXPLODE_MTEXT = yes
    ACAD_IGNORE_FROZEN_LAYERS = no
    ACAD_IGNORE_HIDDEN_LAYERS = yes
    ACAD_IGNORE_UCS = no
    ACAD_IGNORE_VIEWPORT_FROZEN_LAYERS = no
    ACAD_INTERPRET_EXTENDED_DATA = yes
    ACAD_LIST_ATTRIBUTE_ENTITY_DATA = yes
    ACAD_LIST_DYNAMIC_BLOCK_ATTRIBUTES = yes
    ACAD_LIST_EXTENDED_DATA = yes
    ACAD_METAFILE = acad
    ACAD_PRESERVE_CLIPPED_RASTERS = no
    ACAD_PRESERVE_COMPLEX_HATCHES = no
    ACAD_PRESERVE_INSERTS = no
    ACAD_QUERY_FEATURE_TYPES_FOR_MERGE_FILTERS = Yes
    ACAD_READ_AS_2_5D = no
    ACAD_READ_AS_GEOM_INSTANCES = no
    ACAD_READ_DYNAMIC_BLOCK_ATTRIBUTES = no
    ACAD_READ_GROUPS = no
    ACAD_READ_MODEL_SPACE = yes
    ACAD_READ_PAPER_SPACE = NO
    ACAD_READ_PROXY_GRAPHICS = yes
    ACAD_READ_RASTERS = yes
    ACAD_READ_REGIONS_AS_AREAS = yes
    ACAD_READ_SYS_VARS = no
    ACAD_READ_USER_DICTIONARIES = no
    ACAD_READ_XREFS = no
    ACAD_RESOLVE_BLOCKS = yes
    ACAD_RESOLVE_DIMENSIONS = yes
    ACAD_RESOLVE_ENTITY_COLOR = yes
    ACAD_STORE_BULGE_INFO = no
    ACAD_STORE_INSERT_POINT = no
    ACAD_STORE_LAYER_INFO = no
    ACAD_STORE_SPLINE_DEFS = yes
    ACAD_STRUCTURE_EXTENDED_DATA = no
    ACAD_USE_BLOCK_HEADER_LAYER = yes
    ACAD_USE_BLOCK_LAYER_INFO = no
    ACAD_USE_NEW_PAPER_SPACE_PARAMETERS = yes
    ACAD_USE_SEARCH_ENVELOPE = NO
    ACAD_VISIBLE_ATTRIBUTES_AS_TEXT = yes
    ACAD_XRECORD_READING = None
    ATTRIBUTES = 0,,PG-AA,,PG-AS,,PG-LI,,PG-LP,,PS01-AS,,PS01-AU,,PS01-LP,
    ATTRS_TO_EXPOSE = autocad_source_filename fme_feature_type fme_basename
    ATTR_ACCUM_MODE = Only Use Result
    COMBINE_GEOM = Use Result
    DATASET = $(dxf)
    FORMAT = ACAD
    GEOMETRY_TYPES = 0,""",fme_arc,fme_area,fme_collection,fme_ellipse,fme_line,fme_point,fme_raster,fme_solid,fme_surface,fme_text""",PG-AA,""",fme_arc,fme_area,fme_collection,fme_ellipse,fme_line,fme_point,fme_raster,fme_solid,fme_surface,fme_text""",PG-AS,""",fme_arc,fme_area,fme_collection,fme_ellipse,fme_line,fme_point,fme_raster,fme_solid,fme_surface,fme_text""",PG-LI,""",fme_arc,fme_area,fme_collection,fme_ellipse,fme_line,fme_point,fme_raster,fme_solid,fme_surface,fme_text""",PG-LP,""",fme_arc,fme_area,fme_collection,fme_ellipse,fme_line,fme_point,fme_raster,fme_solid,fme_surface,fme_text""",PS01-AS,""",fme_arc,fme_area,fme_collection,fme_ellipse,fme_line,fme_point,fme_raster,fme_solid,fme_surface,fme_text""",PS01-AU,""",fme_arc,fme_area,fme_collection,fme_ellipse,fme_line,fme_point,fme_raster,fme_solid,fme_surface,fme_text""",PS01-LP,""",fme_arc,fme_area,fme_collection,fme_ellipse,fme_line,fme_point,fme_raster,fme_solid,fme_surface,fme_text"""
    INTERACT = NONE
    ORDER_RESULTS = No
    OUTPUT_ADD_SCHEMA_ATTRIBUTES = NO
    OUTPUT_FEATURES_DISPLAY = Schema and Data Features
    <OTHER> -> AttributeSplitter
AttributeSplitter
    ATTR_NAME = autocad_source_filename
    DELIMITER = \
    DROP_EMPTY_PARTS = NO
    LIST_NAME = _list
    TRIM_TYPE = BOTH
    -> ListElementCounter
ListElementCounter
    CNT_ATTR = _element_count
    LIST_NAME = _list{}
    -> AttributeCreator
AttributeCreator
    ATTR_TABLE = SET_TO Posicion (real64) = @Evaluate(@Value(_element_count)-1)
    -> AttributeManager_8
AttributeManager_8
    ATTR_TABLE:
      SET_TO Fichero (varchar(200)) = @Value(_list{@Value(Posicion)})
      REMOVE Posicion (real64)
      REMOVE autocad_source_filename (buffer)
      REMOVE fme_basename (buffer)
      REMOVE _list{} (varchar(200))
      REMOVE _element_count (uint64)
    -> StringReplacer
StringReplacer
    CASE = NO
    FIND_TEXT = .DXF
    NO_MATCH = _FME_NO_OP_
    REGEXP = NO
    SRC_ATTRS = Fichero
    -> AttributeExposer
AttributeExposer
    ATTR_TABLE = autocad_text_string,
    -> Tester_5
Note: Filtro niveles que deben ir en CROQUIS
Tester_5
    BOOL_OP = OR
    TEST_CLAUSE:
      TEST @Value(fme_feature_type) = PG-AA
      TEST @Value(fme_feature_type) = PG-TL
      TEST @Value(fme_feature_type) = PG-LI
      TEST @Value(fme_feature_type) = PG-LP
      TEST @Value(fme_feature_type) = PG-TL
      TEST @Value(fme_feature_type) = PG-TP
    TEST_MODE = TEST
    PASSED -> GeometryFilter
GeometryFilter
    FILTER_MODE = SIMPLE
    FILTER_MULTI = FILTER_TYPES]"Text Line"]FME_CONTROLLER_QUERY_FILE]]FME_CONTROLLER_CHOICE]Simple
    Text -> Tester_11
    Curve -> MapnikRasterizer [Line]
Note: Descarto texto "PARCELA"
Tester_11
    BOOL_OP = OR
    TEST_CLAUSE = CASE_INSENSITIVE_TEST @Value(autocad_text_string) NOT_CONTAINS PARCELA
    TEST_MODE = CASE_INSENSITIVE_TEST
    PASSED -> MapnikRasterizer [Text]
Note: Se genera un archivo raster por cada REFCAT
MapnikRasterizer
    BACKGROUND_COLOR = 1,1,1
    BACKGROUND_COLOR_ALPHA = 0.0
    COLROW_OR_SPACING = CellSize
    GROUP_BY = Fichero
    INTERPRETATION_TYPE = RGBA32
    LAYER_CARDINALITY = Each rendering rule is a layer
    MAPNIK_CONFIG = Text;text;"__ignore__text-properties-group;FME_DISCLOSURE_OPEN;name;autocad_text_string;face-name;Arial;size;20;__ignore__color-group;FME_DISCLOSURE_OPEN;fill;0,0,0;opacity;1;halo-fill;1,1,1;halo-radius;0;__ignore__positioning-group;FME_DISCLOSURE_CLOSED;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_CLOSED;comp-op;src-over;FME_CONTROLLER_QUERY_FILE;plugins/mapnik/text.fme;FME_CONTROLLER_CHOICE;text";Line;line;"__ignore__color-group;FME_DISCLOSURE_OPEN;stroke;0,0,0;stroke-opacity;1;__ignore__line-style-group;;stroke-width;1;stroke-linejoin;miter;stroke-linecap;butt;stroke-dasharray;;stroke-miterlimit;4;__ignore__positioning-group;FME_DISCLOSURE_CLOSED;offset;0;__ignore__smoothing-group;;stroke-gamma;1;stroke-gamma-method;power;smooth;0;rasterizer;full;__ignore__comp-group;FME_DISCLOSURE_CLOSED;comp-op;src-over;FME_CONTROLLER_QUERY_FILE;plugins/mapnik/line.fme;FME_CONTROLLER_CHOICE;line"
    SPACING = 0.05
    SPECIFY_GROUND_EXTENTS = Use input data ground extents
    RASTER -> CROQUIS [Passed]
CROQUIS: FeatureWriter
    DATASET = $(salida)\@Value(Fichero)
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
